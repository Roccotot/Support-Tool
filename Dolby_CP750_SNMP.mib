DOLBY-CP750-MIB

DEFINITIONS ::= BEGIN

IMPORTS
         MODULE-IDENTITY, OBJECT-TYPE, NOTIFICATION-TYPE
                FROM SNMPv2-SMI

         MODULE-COMPLIANCE, OBJECT-GROUP, NOTIFICATION-GROUP
                FROM SNMPv2-CONF

         dolbyModules
                FROM DOLBY-SMI

         cinemaProcessorReg
                FROM DOLBY-GLOBAL-REG

         cinemaProcessors
                FROM DOLBY-PRODUCTS-MIB;


dolbyCP750MIBModule MODULE-IDENTITY

                LAST-UPDATED
                                "200902101948Z"
                ORGANIZATION
                                "Dolby Laboratories Inc."
                CONTACT-INFO
                                "Steve Oddo
                                 email: sjo@dolby.com"
                DESCRIPTION
                                "The Dolby Laboratories CP750
                                 product MIB module"
                REVISION
                                "200902101948Z"

                DESCRIPTION     "Initial version - preliminary"

                ::= {dolbyModules 7}
--

-- Identity registration

--


cp750Reg            OBJECT IDENTIFIER     ::= { cinemaProcessorReg 2 }
 
--

-- object definitions

--

cp750Root           OBJECT IDENTIFIER       ::= { cinemaProcessors 2 }

cp750Info           OBJECT IDENTIFIER       ::= { cp750Root 1 }
cp750Status         OBJECT IDENTIFIER       ::= { cp750Root 2 }
cp750Devices        OBJECT IDENTIFIER       ::= { cp750Root 3 }
cp750Actions        OBJECT IDENTIFIER       ::= { cp750Root 4 }
 
--

-- local administration

--


cp750SerialNumber    OBJECT-TYPE
                     SYNTAX        INTEGER
                     MAX-ACCESS    read-only
                     STATUS         current
                     DESCRIPTION
                             "The serial number of the CP750 physical hardware."

                     ::=    { cp750Info 1 }

 cp750AssetTag        OBJECT-TYPE
                      SYNTAX        OCTET STRING (SIZE(0..31))
                      MAX-ACCESS    read-write
                      STATUS         current
                      DESCRIPTION
                              "The customer-specified label for this CP750."

                      ::=    { cp750Info 2 }
 
--

-- signal status

--


cp750DigitalInputValid1    OBJECT-TYPE
                           SYNTAX        INTEGER { notAvailable(0),
                                                   valid(1),
                                                   invalid(2)
                                                 }
                           MAX-ACCESS    read-only
                           STATUS        current
                           DESCRIPTION
                                   "The current status of the bitstream at Digital Input 1."

                           ::=    { cp750Status 1 }

cp750DigitalInputValid2    OBJECT-TYPE
                           SYNTAX        INTEGER { notAvailable(0),
                                                   valid(1),
                                                   invalid(2)
                                                 }
                            MAX-ACCESS    read-only
                            STATUS        current
                            DESCRIPTION
                                    "The current status of the bitstream at Digital Input 2."

                            ::=    { cp750Status 2 }

cp750DigitalInputValid3    OBJECT-TYPE
                           SYNTAX        INTEGER { notAvailable(0),
                                                   valid(1),
                                                   invalid(2)
                                                 }
                            MAX-ACCESS    read-only
                            STATUS        current
                            DESCRIPTION
                                    "The current status of the bitstream at Digital Input 3."

                            ::=    { cp750Status 3 }

cp750DigitalInputValid4    OBJECT-TYPE
                           SYNTAX        INTEGER { notAvailable(0),
                                                   valid(1),
                                                   invalid(2)
                                                 }
                            MAX-ACCESS    read-only
                            STATUS        current
                            DESCRIPTION
                                    "The current status of the bitstream at Digital Input 4."

                            ::=     { cp750Status 4 }

cp750InputSelection         OBJECT-TYPE
                            SYNTAX        OCTET STRING (SIZE (0..15))
                            MAX-ACCESS    read-only
                            STATUS        current
                            DESCRIPTION
                                    "The currently selected input.
                                     Valid values are 'dig_1', 'dig_2', 'dig_3',
                                     'dig_4', 'analog', 'non_sync', 'mic', and 'last'."

                            ::=    { cp750Status 5 }
cp750FaderLevel             OBJECT-TYPE
                            SYNTAX INTEGER (0..100)
                            MAX-ACCESS     read-only
                            STATUS           current
                            DESCRIPTION
                                    "The current CP750 Fader setting."

                            ::=    { cp750Status 6 }
cp750BitstreamFormat        OBJECT-TYPE
                            SYNTAX        OCTET STRING (SIZE (0..15))
                            MAX-ACCESS    read-only
                            STATUS        current
                            DESCRIPTION
                                    "The encoding of the bitstream on the selected input.
                                     Valid values are 'PCM', 'Dolby_Digital', 'Dolby_E',
                                     and 'n_a'."

                            ::=    { cp750Status 7 }
 
cp750DecodeMode             OBJECT-TYPE
                            SYNTAX        OCTET STRING (SIZE (0..15))
                            MAX-ACCESS    read-only
                            STATUS        current
                            DESCRIPTION
                                    "The current decoding configuration on the signal path.
                                     Valid values are 'lr_discrete', 'prologic', 'prologic_2',
                                    'auto', 'n_a', and 'invalid'."

                            ::=    { cp750Status 8 }


cp750MuteStatus             OBJECT-TYPE
                            SYNTAX        INTEGER { notAvailable(0),
                                                    unmuted(1),
                                                    muted(2)
                                                  }
                             MAX-ACCESS    read-only
                             STATUS        current
                             DESCRIPTION
                                    "The current state of the Front Panel Mute."

                             ::=    { cp750Status 9 }


cp750RelayStatus             OBJECT-TYPE
                              SYNTAX        INTEGER { notAvailable(0),
                                                      engaged(1),
                                                      disengaged(2)
                                                    } 
                              MAX-ACCESS    read-only
                              STATUS        current
                              DESCRIPTION
                                      "The current state of the output relays."

                              ::=    { cp750Status 10 }
 
cp750MeterLevels              OBJECT-TYPE
                              SYNTAX        OCTET STRING (SIZE (0..31))
                              MAX-ACCESS    read-only
                              STATUS        current
                              DESCRIPTION
                                      "Meter readings as a string 'L C R LFE Ls Rs Le Re'.
                                       Two bytes per channel with a space between each channel.
                                       Range from 0 to 60. ex:  10 55 00 60 10 01 77 78."

                              ::=    { cp750Status 11 }
 
--

-- Notifications

--


cp750Events                   OBJECT IDENTIFIER    ::= { cp750Root 5 }
cp750FailureEvent             NOTIFICATION-TYPE
                              OBJECTS         {cp750InputSelection,
                                               cp750MuteStatus,
                                               cp750RelayStatus,
                                               cp750MeterLevels
                                              }
                              STATUS         current
                              DESCRIPTION
                                      "A component has failed."

                              ::= { cp750Events 1 }
 
---

--- Conformance statements

---


cp750Conformances             OBJECT IDENTIFIER     ::= { cp750Reg 1 }
cp750Groups                   OBJECT IDENTIFIER     ::= { cp750Conformances 1 }
cp750InfoGroup                OBJECT-GROUP
                              OBJECTS { cp750SerialNumber,
                                        cp750AssetTag
                                      }
                              STATUS    current
                              DESCRIPTION
                                      "Informational objects required for
                                       the basic implementation of the CP750 MIB."

                              ::= { cp750Groups 1 }

 
cp750StatusGroup              OBJECT-GROUP
                              OBJECTS { cp750DigitalInputValid1,
                                        cp750DigitalInputValid2,
                                        cp750DigitalInputValid3,
                                        cp750DigitalInputValid4,
                                        cp750InputSelection,
                                        cp750FaderLevel,
                                        cp750BitstreamFormat,
                                        cp750DecodeMode,
                                        cp750MuteStatus,
                                        cp750RelayStatus,
                                        cp750MeterLevels
                                      }
                               STATUS    current
                               DESCRIPTION
                                       "Status objects required for the basic
                                        implementation of the CP750 MIB."

                               ::= { cp750Groups 2 }
 
cp750EventGroup                NOTIFICATION-GROUP
                               NOTIFICATIONS    { cp750FailureEvent }
                               STATUS    current
                               DESCRIPTION
                                       "Events for the CP750."

                               ::= { cp750Groups 3 }

cp750Compliances    OBJECT IDENTIFIER     ::= { cp750Conformances 2 }
 
cp750BasicCompl        MODULE-COMPLIANCE
                       STATUS    current
                       DESCRIPTION
                               "The basic implementation requirements
                                for the CP750 MIB."
                       MODULE
                                MANDATORY-GROUPS { cp750InfoGroup,
                                                   cp750StatusGroup,
                                                   cp750EventGroup
                                                 }
                       ::= { cp750Compliances 1 }
 
 
 END
